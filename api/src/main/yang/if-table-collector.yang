module if-table-collector {
    yang-version 1;
    namespace "urn:net:donaldh:if-table-collector";
    prefix "if-table-collector";

    import yang-ext { prefix ext; }
    
    import network-topology {
        prefix "nt";
    }
    
    revision "2017-02-22" {
        description "Initial revision of if-table-collector model";
    }

    grouping snmp-attrs-group {
        leaf snmp-community {
            type string;
        }
        leaf snmp-port {
            type uint32;
            default 161;
        }
        leaf poll-interval {
            description "Polling interval in seconds";
            type uint32;
            default 60;
        }
    }

    augment "/nt:network-topology/nt:topology/nt:node" {
        ext:augment-identifier "snmp-attrs";
        uses snmp-attrs-group;
    }
}
